// SPDX-FileCopyrightText: Copyright (C) 2021-2026 Software Radio Systems Limited
// SPDX-License-Identifier: BSD-3-Clause-Open-MPI

module nrcelldu-sib-extensions {
    yang-version 1.1;
    namespace "urn:ocudu-nrcelldu-sib-extension:1.0";
    prefix "ocudu-nrcelldu-sib";

    organization "Software Radio Systems Ltd";
    description "The module defines YANG extensions needed for OCUDU
                 Copyright (c) 2024-2026 Software Radio Systems. All rights reserved.";
    revision 2026-09-10 { description "Move the fixed ETWS/CMAS content into a test sub-container."; }
    revision 2026-06-03 { description "Initial version: si_window_length, si_sched_info list, RRC UE timers
                                       (t300/t301/t310/n310/t311/n311/t319) and ETWS/CMAS warning messages."; }

    grouping sib_extensions_subtree {
        description "OCUDU extension of the NRCellDU SIB / SI scheduling config.";

        container ocudu_nrcelldu_sib_extensions {
            leaf si_window_length {
                description "Length of the SI scheduling window in slots. Must be <= the SI message period.";
                type uint16 { range "5 | 10 | 20 | 40 | 80 | 160 | 320 | 640 | 1280"; }
                default 160;
            }

            list si_sched_info {
                description "Scheduling information for each SI message broadcast by the gNB.";
                key "id";

                leaf id {
                    description "Ordering key for this SI-message entry. Not forwarded to srsRAN.";
                    type uint8;
                }
                leaf si_period {
                    description "SI-message scheduling period in radio frames.";
                    type uint16 { range "8 | 16 | 32 | 64 | 128 | 256 | 512"; }
                    default 32;
                }
                leaf-list sib_mapping {
                    description "SIB types mapped into this SI message (SIB numbers must not be repeated).";
                    type uint8 { range "2 | 3 | 4 | 5 | 6 | 7 | 8 | 16 | 19"; }
                }
                leaf si_window_position {
                    description "SI window position of this SI message (release-17 SI-SchedulingInfo2). If unset, "
                              + "OCUDU derives it.";
                    type uint16 { range "1..256"; }
                }
            }

            leaf t300 {
                description "RRC Connection Establishment timer in ms (started on RRCSetupRequest).";
                type uint16 { range "100 | 200 | 300 | 400 | 600 | 1000 | 1500 | 2000"; }
                default 1000;
            }
            leaf t301 {
                description "RRC Connection Re-establishment timer in ms (started on RRCReestablishmentRequest).";
                type uint16 { range "100 | 200 | 300 | 400 | 600 | 1000 | 1500 | 2000"; }
                default 1000;
            }
            leaf t310 {
                description "Out-of-sync timer in ms (started after N310 consecutive out-of-sync indications).";
                type uint16 { range "0 | 50 | 100 | 200 | 500 | 1000 | 2000"; }
                default 1000;
            }
            leaf n310 {
                description "Out-of-sync counter; on reaching this value while T310 is stopped, T310 is started.";
                type uint8 { range "1 | 2 | 3 | 4 | 6 | 8 | 10 | 20"; }
                default 1;
            }
            leaf t311 {
                description "RRC Connection Re-establishment procedure timer in ms.";
                type uint16 { range "1000 | 3000 | 5000 | 10000 | 15000 | 20000 | 30000"; }
                default 3000;
            }
            leaf n311 {
                description "In-sync counter; on reaching this value while T310 is running, T310 is stopped.";
                type uint8 { range "1 | 2 | 3 | 4 | 5 | 6 | 8 | 10"; }
                default 1;
            }
            leaf t319 {
                description "RRC Connection Resume timer in ms (started on RRCResumeRequest).";
                type uint16 { range "100 | 200 | 300 | 400 | 600 | 1000 | 1500 | 2000"; }
                default 1000;
            }

            container etws {
                description "Earthquake and Tsunami Warning System message parameters (broadcast over SIB6/SIB7).";

                container test {
                    description "Fixed content broadcast from the cell start, for testing purposes.";

                    leaf message_id {
                        description "ETWS message ID (TS 23.041).";
                        type uint16;
                        default 4356;
                    }
                    leaf serial_num {
                        description "ETWS message serial number (TS 23.041).";
                        type uint16;
                        default 12288;
                    }
                    leaf warning_type {
                        description "ETWS warning type (TS 23.041).";
                        type uint16;
                        default 2432;
                    }
                    leaf data_coding_scheme {
                        description "CBS data coding scheme used for the warning message (TS 23.038).";
                        type uint8;
                        default 0;
                    }
                    leaf warning_message {
                        description "ETWS warning message. Required only if SIB7 is scheduled; otherwise leave unset.";
                        type string;
                    }
                }
            }

            container cmas {
                description "Commercial Mobile Alert Service message parameters (broadcast over SIB8).";

                container test {
                    description "Fixed content broadcast from the cell start, for testing purposes.";

                    leaf message_id {
                        description "CMAS message ID (TS 23.041).";
                        type uint16;
                        default 4370;
                    }
                    leaf serial_num {
                        description "CMAS message serial number (TS 23.041).";
                        type uint16;
                        default 12291;
                    }
                    leaf data_coding_scheme {
                        description "CBS data coding scheme used for the warning message (TS 23.038).";
                        type uint8;
                        default 0;
                    }
                    leaf warning_message {
                        description "CMAS warning message.";
                        type string;
                    }
                }
            }
        }
    }
}
