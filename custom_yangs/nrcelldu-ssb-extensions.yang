// SPDX-FileCopyrightText: Copyright (C) 2021-2026 Software Radio Systems Limited
// SPDX-License-Identifier: BSD-3-Clause-Open-MPI

module nrcelldu-ssb-extensions {
    yang-version 1.1;
    namespace "urn:ocudu-nrcelldu-ssb-extension:1.0";
    prefix "ocudu-nrcelldu-ssb";
   
    organization "Software Radio Systems Ltd";
    description "The module defines YANG extensions needed for OCUDU
                 Copyright (c) 2024-2026 Software Radio Systems. All rights reserved.";
    revision 2026-04-02 { description "Renamed srs instances to ocudu";}
    revision 2025-01-08 { description "Initial version"; }

    grouping ssb_extensions_subtree {
        description "OCUDU Extension of 3gpp SSB config";

        container ocudu_nrcelldu_ssb_extensions {

            leaf ssb_period {
                description "Period of SSB scheduling in milliseconds";
                type int32;
                default "10";
            }

            leaf ssb_block_power_dbm {
                description "SS_PBCH_power_block in dBm";
                type ssb_block_power;
                default "-16";
            }
        }
    }

    typedef ssb_block_power {
        type int32 { range -60..50; }
        units dbm;
    }
}
