// SPDX-FileCopyrightText: Copyright (C) 2021-2026 Software Radio Systems Limited
// SPDX-License-Identifier: BSD-3-Clause-Open-MPI

module nrcelldu-extensions {
    yang-version 1.1;
    namespace "urn:ocudu-nrcelldu-extension:1.0";
    prefix "ocudu-nrcelldu";

    import _3gpp-common-managed-element { prefix me3gpp; }
    import _3gpp-nr-nrm-gnbdufunction { prefix gnbdu3gpp; }
    import _3gpp-nr-nrm-nrcelldu { prefix nrcelldu3gpp; }
    
    import nrcelldu-ssb-extensions { prefix ocudu-nrcelldu-ssb; }
    import nrcelldu-prach-extensions { prefix ocudu-nrcelldu-prach; }
    import nrcelldu-ofh-extensions { prefix ocudu-nrcelldu-ofh; }
    import nrcelldu-pdsch-extensions { prefix ocudu-nrcelldu-pdsch; }
    import nrcelldu-pusch-extensions { prefix ocudu-nrcelldu-pusch; }
    import nrcelldu-pucch-extensions { prefix ocudu-nrcelldu-pucch; }
    import nrcelldu-pdcch-extensions { prefix ocudu-nrcelldu-pdcch; }
    import nrcelldu-csi-extensions { prefix ocudu-nrcelldu-csi; }
    import nrcelldu-srs-extensions { prefix ocudu-nrcelldu-srs; }
    import nrcelldu-base-extensions { prefix ocudu-nrcelldu-base; }
    import nrcelldu-tdd-extensions { prefix ocudu-nrcelldu-tdd; }
    import nrcelldu-mac-cell-group-extensions { prefix ocudu-nrcelldu-mac-cell-group; }
    import nrcelldu-sib-extensions { prefix ocudu-nrcelldu-sib; }
    import nrcelldu-paging-extensions { prefix ocudu-nrcelldu-paging; }
    import nrcelldu-drx-extensions { prefix ocudu-nrcelldu-drx; }
    import nrcelldu-ntn-extensions { prefix ocudu-nrcelldu-ntn; }
    import nrcelldu-scheduler-extensions { prefix ocudu-nrcelldu-scheduler; }

    organization "Software Radio Systems Ltd";
    description "The module defines YANG extensions needed for OCUDU
                 Copyright (c) 2024-2026 Software Radio Systems. All rights reserved.";
    revision 2026-08-06 { description "Added ntn sub-extension"; }
    revision 2026-05-13 { description "Added pusch/pucch/pdcch/csi/srs sub-extensions"; }
    revision 2026-04-02 { description "Renamed srs instances to ocudu";}
    revision 2025-01-08 { description "Initial version"; }

    grouping nrcelldu_extensions_subtree {

        container ocudu_nrcelldu_extensions {
            description "OCUDU extension of 3gpp NRCellDU config";

            uses ocudu-nrcelldu-base:base_extensions_subtree;
            uses ocudu-nrcelldu-ofh:ofh_extensions_subtree;
            uses ocudu-nrcelldu-ssb:ssb_extensions_subtree;
            uses ocudu-nrcelldu-prach:prach_extensions_subtree;
            uses ocudu-nrcelldu-pdsch:pdsch_extensions_subtree;
            uses ocudu-nrcelldu-pusch:pusch_extensions_subtree;
            uses ocudu-nrcelldu-pucch:pucch_extensions_subtree;
            uses ocudu-nrcelldu-pdcch:pdcch_extensions_subtree;
            uses ocudu-nrcelldu-csi:csi_extensions_subtree;
            uses ocudu-nrcelldu-srs:srs_extensions_subtree;
            uses ocudu-nrcelldu-tdd:tdd_extensions_subtree;
            uses ocudu-nrcelldu-mac-cell-group:mac_cell_group_extensions_subtree;
            uses ocudu-nrcelldu-sib:sib_extensions_subtree;
            uses ocudu-nrcelldu-paging:paging_extensions_subtree;
            uses ocudu-nrcelldu-drx:drx_extensions_subtree;
            uses ocudu-nrcelldu-ntn:ntn_extensions_subtree;
            uses ocudu-nrcelldu-scheduler:scheduler_extensions_subtree;
            uses ocudu-nrcelldu-scheduler:ta_extensions_subtree;
        }
    }

    augment /me3gpp:ManagedElement/gnbdu3gpp:GNBDUFunction/nrcelldu3gpp:NRCellDU/nrcelldu3gpp:attributes {
        uses nrcelldu_extensions_subtree;
    }
}
