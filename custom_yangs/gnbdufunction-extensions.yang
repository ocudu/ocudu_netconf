// SPDX-FileCopyrightText: Copyright (C) 2021-2026 Software Radio Systems Limited
// SPDX-License-Identifier: BSD-3-Clause-Open-MPI

module gnbdufunction-extensions {
    yang-version 1.1;
    namespace "urn:ocudu-gnbdufunction-extension:1.0";
    prefix "ocudu-gnbdufunction";

    import _3gpp-common-managed-element { prefix me3gpp; }
    import _3gpp-nr-nrm-gnbdufunction { prefix gnbdu3gpp; }
    import _3gpp-nr-nrm-ep { prefix ep3gpp; }
    import ietf-inet-types { prefix inet; }

    import gnbdufunction-testmode-extensions { prefix ocudu-gnbdufunction-testmode; }
    import expert-phy-extensions { prefix ocudu-expert-phy; }
    import expert-execution-extensions { prefix ocudu-expert-execution; }
    import log-extensions { prefix ocudu-log; }
    import hal-extensions { prefix ocudu-hal; }
    import metrics-extensions { prefix ocudu-metrics; }
    import pcap-extensions { prefix ocudu-pcap; }
    import remote-control-extensions { prefix ocudu-remote-control; }
    import trace-extensions { prefix ocudu-trace; }
    import rudummy-extensions { prefix ocudu-rudummy; }
    import rusdr-extensions { prefix ocudu-rusdr; }
    import qos-extensions { prefix ocudu-qos; }

    organization "Software Radio Systems Ltd";
    description "The module defines YANG extensions needed for OCUDU
                 Copyright (c) 2024-2026 Software Radio Systems. All rights reserved.";
    revision 2026-11-06 { description "Add trace-extensions subtree"; }
    revision 2026-11-03 { description "Add warn_on_drop on GNBDUFunction; add qos and srbs lists (qos-extensions)"; }
    revision 2026-08-07 { description "Add expert-execution-extensions subtree (main pool thread sizing)"; }
    revision 2026-07-01 { description "Add rusdr-extensions subtree (SDR Radio Unit configuration)"; }
    revision 2026-06-23 { description "Add configurable F1-U (GTP-U) bind/peer UDP ports on EP_F1U"; }
    revision 2026-06-08 { description "Allow FQDN (remoteAddress -> inet:host) on EP_F1C; remove remoteAddress on EP_F1U (F1-U peer learned via F1AP signaling)"; }
    revision 2026-06-03 { description "Add expert-phy-extensions subtree";}
    revision 2026-05-04 { description "Add pcap-extensions subtree";}
    revision 2026-04-02 { description "Renamed srs instances to ocudu";}
    revision 2025-01-08 { description "Initial version"; }

    grouping gnbdufunction_extensions_subtree {

        container ocudu_gnbdufunction_extensions {
            description "OCUDU extension of GNBDUFunction";

            uses ocudu-gnbdufunction-testmode:testmode_extensions_subtree;
            uses ocudu-expert-phy:expert_phy_extensions_subtree;
            uses ocudu-expert-execution:expert_execution_extensions_subtree;
            uses ocudu-log:log_extensions_subtree;
            uses ocudu-hal:hal_extensions_subtree;
            uses ocudu-metrics:metrics_extensions_du_subtree;
            uses ocudu-pcap:pcap_extensions_subtree;
            uses ocudu-remote-control:remote_control_extensions_subtree;
            uses ocudu-trace:trace_extensions_du_subtree;
            uses ocudu-rudummy:rudummy_extensions_subtree;
            uses ocudu-rusdr:rusdr_extensions_subtree;
            uses ocudu-qos:qos_extensions_du_subtree;

            leaf warn_on_drop {
                description "Log a warning for packets dropped in F1-U, RLC and MAC
                             due to full queues.";
                type boolean;
                default false;
            }
        }
    }

    augment /me3gpp:ManagedElement/gnbdu3gpp:GNBDUFunction {
        uses gnbdufunction_extensions_subtree;
    }

    deviation /me3gpp:ManagedElement/gnbdu3gpp:GNBDUFunction/ep3gpp:EP_F1C/ep3gpp:attributes/ep3gpp:remoteAddress {
        deviate replace { type inet:host; }
        description "Allow the F1-C peer (gNB-CU-CP) to be addressed by DNS name in Kubernetes
                     deployments. Widen to inet:host so an FQDN validates in the datastore.";
    }

    deviation /me3gpp:ManagedElement/gnbdu3gpp:GNBDUFunction/ep3gpp:EP_F1U/ep3gpp:attributes/ep3gpp:remoteAddress {
        deviate not-supported;
        description "F1-U is GTP-U: the peer (gNB-CU-UP) transport address is learned via F1AP
                     bearer-context signaling, not statically configured. 3GPP marks
                     remoteAddress mandatory, so remove it to forbid it being set.";
    }

    augment /me3gpp:ManagedElement/gnbdu3gpp:GNBDUFunction/ep3gpp:EP_F1U/ep3gpp:attributes {
        container ocudu_ep_f1u_extensions {
            description "OCUDU F1-U transport extensions. 3GPP EP_F1U models only the local
                         address (localAddress); these leaves add the GTP-U UDP ports.";

            leaf bind_port {
                type inet:port-number;
                default 2152;
                description "Local UDP port the F1-U (GTP-U) socket binds to.
                             Defaults to 2152 per 3GPP TS 29.281 Sec. 4.4.2.3.";
            }
            leaf peer_port {
                type inet:port-number;
                default 2152;
                description "Remote UDP port the F1-U (GTP-U) socket sends to.
                             Defaults to 2152 per 3GPP TS 29.281 Sec. 4.4.2.3.";
            }
        }
    }
}
