// SPDX-FileCopyrightText: Copyright (C) 2021-2026 Software Radio Systems Limited
// SPDX-License-Identifier: BSD-3-Clause-Open-MPI

module hal-extensions {
    yang-version 1.1;
    namespace "urn:ocudu-hal-extension:1.0";
    prefix "ocudu-hal";

    organization "Software Radio Systems Ltd";
    description "The module defines YANG extensions needed for OCUDU
                 Copyright (c) 2024-2026 Software Radio Systems. All rights reserved.";
    revision 2026-04-02 { description "Renamed srs instances to ocudu";}
    revision 2025-01-08 { description "Initial version"; }


    grouping hal_extensions_subtree {
        description "OCUDU Extension for Hardware Abstraction Layer";

        container ocudu_hal_extensions {
            container bbdev_hwacc {
                description "BBDEV-based hardware-acceleration configuration parameters";

                leaf hwacc_type {
                    description "Type of BBDEV hardware-accelerator (acc100, acc200, vrb1)";
                    type enumeration {
                        enum acc100;
                        enum acc200;
                        enum vrb1;
                    }
                }

                leaf id {
                    description "ID of the BBDEV-based hardware-accelerator";
                    type uint16;
                }

                container pdsch_enc {
                    description "Hardware-accelerated PDSCH encoding functions configuration";

                    leaf nof_hwacc {
                        description "Number of hardware-accelerated PDSCH encoding functions";
                        type uint8 {
                            range "0..64";
                        }
                    }

                    leaf cb_mode {
                        description "Operation mode of the PDSCH encoder (CB = true, TB = false)";
                        type boolean;
                        default false;
                    }

                    leaf max_buffer_size {
                        description "Maximum supported buffer size in bytes (CB mode forced for larger TBs)";
                        type uint32;
                    }

                    leaf dedicated_queue {
                        description "Use dedicated hardware queues (true) or shared queues (false)";
                        type boolean;
                        default true;
                    }
                }

                container pusch_dec {
                    description "Hardware-accelerated PUSCH decoding functions configuration";

                    leaf nof_hwacc {
                        description "Number of hardware-accelerated PUSCH decoding functions";
                        type uint8 {
                            range "0..64";
                        }
                    }

                    leaf harq_context_size {
                        description "Size of the HARQ context repository";
                        type uint32;
                    }

                    leaf force_local_harq {
                        description "Force using host memory for the HARQ buffer";
                        type boolean;
                        default false;
                    }

                    leaf dedicated_queue {
                        description "Use dedicated hardware queues (true) or shared queues (false)";
                        type boolean;
                        default true;
                    }
                }

                leaf msg_mbuf_size {
                    description "Size of mbufs for unencoded and unrate-matched messages (in bytes)";
                    type uint32;
                }

                leaf rm_mbuf_size {
                    description "Size of mbufs for encoded and rate-matched messages (in bytes)";
                    type uint32;
                }

                leaf nof_mbuf {
                    description "Number of mbufs in each memory pool";
                    type uint32;
                }
            }

            leaf eal_args {
                description "EAL configuration parameters used to initialize DPDK";
                type string;
            }
       }
    }
}
