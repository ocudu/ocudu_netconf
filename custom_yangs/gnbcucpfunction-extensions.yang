// SPDX-FileCopyrightText: Copyright (C) 2021-2026 Software Radio Systems Limited
// SPDX-License-Identifier: BSD-3-Clause-Open-MPI

module gnbcucpfunction-extensions {
    yang-version 1.1;
    namespace "urn:ocudu-gnbcucpfunction-extension:1.0";
    prefix "ocudu-gnbcucpfunction";

    import _3gpp-common-managed-element { prefix me3gpp; }
    import _3gpp-nr-nrm-gnbcucpfunction { prefix gnbcucp3gpp; }
    import _3gpp-nr-nrm-ep { prefix ep3gpp; }
    import _3gpp-nr-nrm-nrcellcu { prefix nrcellcu3gpp; }
    import _3gpp-nr-nrm-cesmanagementfunction { prefix cesmf3gpp; }
    import _3gpp-5g-common-yang-types { prefix types5g3gpp; }
    import ietf-inet-types { prefix inet; }

    import log-extensions { prefix ocudu-log; }
    import metrics-extensions { prefix ocudu-metrics; }
    import pcap-extensions { prefix ocudu-pcap; }
    import remote-control-extensions { prefix ocudu-remote-control; }
    import trace-extensions { prefix ocudu-trace; }
    import qos-extensions { prefix ocudu-qos; }

    organization "Software Radio Systems Ltd";
    description "The module defines YANG extensions needed for OCUDU
                 Copyright (c) 2024-2026 Software Radio Systems. All rights reserved.";
    revision 2026-11-06 { description "Add trace-extensions subtree"; }
    revision 2026-11-05 { description "Make the CESManagementFunction load-threshold lists optional on NRCellCU, so energySavingControl can be set on its own"; }
    revision 2026-11-03 { description "Add qos list (qos-extensions)"; }
    revision 2026-08-20 { description "Replace nof_i_rnti_ue_bits with full_i_rnti_profile/short_i_rnti_profile, following the I-RNTI composition of TS 38.300 Annex F"; }
    revision 2026-08-14 { description "Add cu_cp.rrc configuration subtree"; }
    revision 2026-08-10 { description "Add top-level cu_cp options: connection/UE/DRB limits, inactivity timer and RRC-inactive parameters"; }
    revision 2026-08-10 { description "Add cu_cp.security configuration subtree"; }
    revision 2026-07-01 { description "Add remaining cu_cp.amf configuration on EP_NgC: bind_interface, SCTP socket tuning, no_core, amf_reconnection_retry_time, procedure_timeout"; }
    revision 2026-06-29 { description "Add optional nRTAC leaf so a standalone gNB-CU-CP can set the Tracking Area Code advertised in the NGAP supported-TA list"; }
    revision 2026-06-23 { description "Add configurable NG-C (NGAP/SCTP) AMF port on EP_NgC"; }
    revision 2026-06-08 { description "Allow FQDN (remoteAddress -> inet:host) on EP_NgC; remove remoteAddress on EP_F1C and EP_E1 (CU-CP terminates F1-C/E1 as a server, so the connect address lives on the peer)"; }
    revision 2026-05-28 { description "Add remote-control-extensions subtree"; }
    revision 2026-04-30 { description "Initial version"; }

    typedef security_indication {
        description "Protection indication signalled towards the core for a DRB.";
        type enumeration {
            enum required;
            enum preferred;
            enum not_needed;
        }
    }

    typedef algorithm_pref_list {
        description "Comma-separated, ordered list of security algorithms, most preferred first.
                     The application strips whitespace and lowercases before parsing, so the
                     refining patterns allow spaces around the separators.";
        type string {
            length "1..64";
        }
    }

    grouping gnbcucpfunction_extensions_subtree {

        container ocudu_gnbcucpfunction_extensions {
            description "OCUDU extension of GNBCUCPFunction";

            leaf nRTAC {
                type types5g3gpp:NRTAC;
                description "Tracking Area Code the gNB-CU-CP advertises in the NGAP
                             supported-TA list towards the AMF. 3GPP models nRTAC only on
                             NRCellDU/GNBCUUPFunction, this leaf fills that gap.";
                reference "3GPP TS 23.003, 3GPP TS 38.413";
            }

            leaf max_nof_dus {
                description "Maximum number of DU connections the CU-CP may accept.";
                type uint16;
                default 6;
            }

            leaf max_nof_cu_ups {
                description "Maximum number of CU-UP connections the CU-CP may accept.";
                type uint16;
                default 6;
            }

            leaf max_nof_ues {
                description "Maximum number of UEs the CU-CP may accept.";
                type uint32;
                default 8192;
            }

            leaf max_nof_drbs_per_ue {
                description "Maximum number of data radio bearers per UE.";
                type uint8 { range "1..29"; }
                default 8;
            }

            leaf inactivity_timer {
                description "UE / PDU session / DRB inactivity timer.";
                type uint16 { range "1..7200"; }
                units seconds;
                default 120;
            }

            leaf enable_rrc_inactive {
                description "Whether a UE is moved to RRC inactive on expiry of the inactivity timer.
                             When disabled, the UE is released instead.";
                type boolean;
                default false;
            }

            leaf ran_paging_cycle {
                description "RAN paging cycle for RRC inactive UEs, in radio frames.";
                type uint16 { range "32 | 64 | 128 | 256"; }
                units frames;
                default 32;
            }

            leaf t380 {
                description "RRC inactivity timer T380. Started when the UE receives an RRCRelease
                             carrying a suspend config, stopped on RRCResume.";
                type uint16 { range "5 | 10 | 20 | 30 | 60 | 120 | 360 | 720"; }
                units minutes;
                default 10;
            }

            leaf full_i_rnti_profile {
                description "I-RNTI profile the Full-I-RNTI of a suspended UE is composed with. The
                             profile sets the width of the Local NG-RAN Node Identifier the I-RNTI
                             carries, and so how many of the remaining bits are left for the UE
                             reference.";
                reference "3GPP TS 38.300 table F-1";
                type enumeration {
                    enum profile0;
                    enum profile1;
                    enum profile2;
                    enum profile3;
                }
                default profile0;
            }

            leaf short_i_rnti_profile {
                description "I-RNTI profile the Short-I-RNTI of a suspended UE is composed with. The
                             profile sets the width of the Local NG-RAN Node Identifier the I-RNTI
                             carries, and so how many of the remaining bits are left for the UE
                             reference.";
                reference "3GPP TS 38.300 table F-2";
                type enumeration {
                    enum profile0;
                    enum profile1;
                }
                default profile0;
            }

            leaf request_pdu_session_timeout {
                description "Timeout for requesting a PDU session after the InitialUeMessage is sent to
                             the core; on expiry the UE is released. Must be larger than the cell's T310
                             (cell_cfg/sib/t310), which lives on a different network function and so
                             cannot be cross-checked here.";
                type uint32;
                units seconds;
                default 3;
            }

            container rrc {
                description "RRC-specific configuration, rendered as the cu_cp/rrc YAML subtree.";

                leaf force_reestablishment_fallback {
                    description "Force an RRC re-establishment to fall back to an RRC setup.";
                    type boolean;
                    default false;
                }

                leaf force_resume_fallback {
                    description "Force an RRC resume to fall back to an RRC setup.";
                    type boolean;
                    default false;
                }

                leaf rrc_procedure_guard_time_ms {
                    description "Guard time added to the RRC procedure timeout for message exchange
                                 with the UE.

                                 It must exceed 2 * the SRB maxRetxThreshold * t-PollRetransmit
                                 (TS 38.331 clause 9.2.1), which with the defaults is 2 * 8 * 45 ms =
                                 720 ms. Those SRB parameters are configured per signalling radio
                                 bearer rather than on this network function, so the relationship
                                 cannot be checked here.";
                    type uint32;
                    units milliseconds;
                    default 1000;
                }

                leaf rrc_reject_wait_time_s {
                    description "waitTime signalled in the RRC Reject waitTime IE. The IE is optional
                                 (TS 38.331, Need N): when this leaf is absent the gNB sends an RRC
                                 Reject with no waitTime, so it deliberately carries no default.";
                    type uint8 { range "1..16"; }
                    units seconds;
                }
            }

            container security {
                description "Security configuration, rendered as the cu_cp/security YAML subtree.";

                leaf integrity {
                    description "Default integrity protection indication signalled for DRBs.";
                    type security_indication;
                    default not_needed;
                }

                leaf confidentiality {
                    description "Default confidentiality protection indication signalled for DRBs.";
                    type security_indication;
                    default required;
                }

                leaf nea_pref_list {
                    description "Ordered preference list for selecting the ciphering algorithm (NEA).
                                 NEA0 (null ciphering) is permitted here.";
                    type algorithm_pref_list {
                        pattern "nea[0-3]( *, *nea[0-3])*";
                    }
                    default "nea0,nea2,nea1,nea3";
                }

                leaf nia_pref_list {
                    description "Ordered preference list for selecting the integrity algorithm (NIA).

                                 NIA0 is deliberately not accepted: it is null integrity protection and
                                 the application rejects it outright with 'NIA0 cannot be selected in
                                 the algorithm preferences'.";
                    type algorithm_pref_list {
                        pattern "nia[1-3]( *, *nia[1-3])*";
                    }
                    default "nia2,nia1,nia3";
                }
            }

            uses ocudu-log:log_extensions_subtree;
            uses ocudu-metrics:metrics_extensions_cucp_subtree;
            uses ocudu-pcap:pcap_extensions_subtree;
            uses ocudu-remote-control:remote_control_extensions_subtree;
            uses ocudu-trace:trace_extensions_cucp_subtree;
            uses ocudu-qos:qos_extensions_cucp_subtree;
        }
    }

    augment /me3gpp:ManagedElement/gnbcucp3gpp:GNBCUCPFunction {
        uses gnbcucpfunction_extensions_subtree;
    }

    deviation /me3gpp:ManagedElement/gnbcucp3gpp:GNBCUCPFunction/ep3gpp:EP_NgC/ep3gpp:attributes/ep3gpp:remoteAddress {
        deviate replace { type inet:host; }
        description "3GPP types EP_NgC remoteAddress as an IP address, but in Kubernetes
                     deployments the AMF is reached via a DNS service name (ClusterIPs
                     change across reinstalls). Widen to inet:host so an FQDN validates in
                     the datastore;";
    }

    deviation /me3gpp:ManagedElement/gnbcucp3gpp:GNBCUCPFunction/ep3gpp:EP_F1C/ep3gpp:attributes/ep3gpp:remoteAddress {
        deviate not-supported;
        description "The gNB-CU-CP terminates F1-C as a server: it only binds (localAddress)
                     and never dials the peer, so a remote/connect address is meaningless
                     here. The F1-C connect address is configured on the gNB-DU's EP_F1C
                     instead. 3GPP marks remoteAddress mandatory, so remove it entirely from
                     the CU-CP's EP_F1C to forbid it being set.";
    }

    deviation /me3gpp:ManagedElement/gnbcucp3gpp:GNBCUCPFunction/ep3gpp:EP_E1/ep3gpp:attributes/ep3gpp:remoteAddress {
        deviate not-supported;
        description "The gNB-CU-CP terminates E1 as a server: it only binds (localAddress) and
                     never dials the peer. The E1 connect address is configured on the
                     gNB-CU-UP's EP_E1 instead. 3GPP marks remoteAddress mandatory, so remove
                     it from the CU-CP's EP_E1 to forbid it being set.";
    }

    // The CU-CP switches cells off/on only on energySavingControl (centralized ES). It does not
    // evaluate the distributed-ES load thresholds below, which 3GPP marks min-elements 1; make
    // them optional so an SMO can set energySavingControl without inventing threshold values.
    deviation /me3gpp:ManagedElement/gnbcucp3gpp:GNBCUCPFunction/nrcellcu3gpp:NRCellCU/cesmf3gpp:CESManagementFunction/cesmf3gpp:attributes/cesmf3gpp:intraRatEsActivationOriginalCellLoadParameters {
        deviate replace { min-elements 0; }
    }

    deviation /me3gpp:ManagedElement/gnbcucp3gpp:GNBCUCPFunction/nrcellcu3gpp:NRCellCU/cesmf3gpp:CESManagementFunction/cesmf3gpp:attributes/cesmf3gpp:intraRatEsActivationCandidateCellsLoadParameters {
        deviate replace { min-elements 0; }
    }

    deviation /me3gpp:ManagedElement/gnbcucp3gpp:GNBCUCPFunction/nrcellcu3gpp:NRCellCU/cesmf3gpp:CESManagementFunction/cesmf3gpp:attributes/cesmf3gpp:intraRatEsDeactivationCandidateCellsLoadParameters {
        deviate replace { min-elements 0; }
    }

    deviation /me3gpp:ManagedElement/gnbcucp3gpp:GNBCUCPFunction/nrcellcu3gpp:NRCellCU/cesmf3gpp:CESManagementFunction/cesmf3gpp:attributes/cesmf3gpp:interRatEsActivationOriginalCellParameters {
        deviate replace { min-elements 0; }
    }

    deviation /me3gpp:ManagedElement/gnbcucp3gpp:GNBCUCPFunction/nrcellcu3gpp:NRCellCU/cesmf3gpp:CESManagementFunction/cesmf3gpp:attributes/cesmf3gpp:interRatEsActivationCandidateCellParameters {
        deviate replace { min-elements 0; }
    }

    deviation /me3gpp:ManagedElement/gnbcucp3gpp:GNBCUCPFunction/nrcellcu3gpp:NRCellCU/cesmf3gpp:CESManagementFunction/cesmf3gpp:attributes/cesmf3gpp:interRatEsDeactivationCandidateCellParameters {
        deviate replace { min-elements 0; }
    }

    augment /me3gpp:ManagedElement/gnbcucp3gpp:GNBCUCPFunction/ep3gpp:EP_NgC/ep3gpp:attributes {
        container ocudu_ep_ngc_extensions {
            description "OCUDU NG-C transport extensions. 3GPP EP_NgC models only the AMF
                         address (remoteAddress) and local bind address (localAddress); these
                         leaves add the remaining transport/behaviour knobs, mapped 1:1 to the
                         gNB-CU-CP 'cu_cp.amf.*' config.";

            leaf port {
                type inet:port-number {
                    range "20000..40000";
                }
                default 38412;
                description "SCTP port of the AMF that the gNB-CU-CP connects to for NG-C/NGAP.
                             Defaults to 38412 per 3GPP TS 38.412 Sec. 7.";
            }
            leaf bind_interface {
                type string;
                default "auto";
                description "Network device the CU-CP binds for the N2 interface.
                             'auto' lets the stack pick the interface.";
            }
            leaf no_core {
                type boolean;
                default false;
                description "Allow the gNB-CU-CP to run without a 5G core (e.g. for test mode).";
            }
            leaf amf_reconnection_retry_time {
                type uint32;
                default 1000;
                description "Time to wait after a failed AMF reconnection attempt, in milliseconds.";
            }
            leaf procedure_timeout {
                type uint32;
                default 5000;
                description "Time the NGAP waits for a response from the AMF, in milliseconds.";
            }

            // SCTP socket tuning for the N2/NGAP association. -1 selects the system default.
            leaf sctp_rto_initial {
                type int32;
                default 120;
                description "SCTP initial RTO in milliseconds (-1 for system default).";
            }
            leaf sctp_rto_min {
                type int32;
                default 120;
                description "SCTP minimum RTO in milliseconds (-1 for system default).";
            }
            leaf sctp_rto_max {
                type int32;
                default 500;
                description "SCTP maximum RTO in milliseconds (-1 for system default).";
            }
            leaf sctp_init_max_attempts {
                type int32;
                default 3;
                description "SCTP INIT maximum attempts (-1 for system default).";
            }
            leaf sctp_max_init_timeo {
                type int32;
                default 500;
                description "SCTP maximum INIT timeout in milliseconds (-1 for system default).";
            }
            leaf sctp_hb_interval {
                type int32;
                default 30000;
                description "SCTP heartbeat interval in milliseconds (-1 for system default).";
            }
            leaf sctp_assoc_max_retx {
                type int32;
                default 10;
                description "SCTP association maximum retransmissions (-1 for system default).";
            }
            leaf sctp_nodelay {
                type boolean;
                default false;
                description "Send SCTP messages immediately without any Nagle-like batching.";
            }
        }
    }
}
