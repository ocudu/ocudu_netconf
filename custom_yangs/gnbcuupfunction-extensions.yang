// SPDX-FileCopyrightText: Copyright (C) 2021-2026 Software Radio Systems Limited
// SPDX-License-Identifier: BSD-3-Clause-Open-MPI

module gnbcuupfunction-extensions {
    yang-version 1.1;
    namespace "urn:ocudu-gnbcuupfunction-extension:1.0";
    prefix "ocudu-gnbcuupfunction";

    import _3gpp-common-managed-element { prefix me3gpp; }
    import _3gpp-nr-nrm-gnbcuupfunction { prefix gnbcuup3gpp; }
    import _3gpp-nr-nrm-ep { prefix ep3gpp; }
    import ietf-inet-types { prefix inet; }

    import log-extensions { prefix ocudu-log; }
    import metrics-extensions { prefix ocudu-metrics; }
    import pcap-extensions { prefix ocudu-pcap; }
    import remote-control-extensions { prefix ocudu-remote-control; }
    import trace-extensions { prefix ocudu-trace; }
    import qos-extensions { prefix ocudu-qos; }

    organization "Software Radio Systems Ltd";
    description "The module defines YANG extensions needed for OCUDU
                 Copyright (c) 2024-2026 Software Radio Systems. All rights reserved.";
    revision 2026-11-06 { description "Add trace-extensions subtree"; }
    revision 2026-11-03 { description "Add qos list (qos-extensions)"; }
    revision 2026-07-01 { description "Add CU-UP test_mode extensions on GNBCUUPFunction"; }
    revision 2026-06-23 { description "Add configurable F1-U (GTP-U) bind/peer UDP ports on EP_F1U"; }
    revision 2026-06-08 { description "Allow FQDN (remoteAddress -> inet:host) on EP_E1; remove remoteAddress on EP_F1U and EP_NgU (GTP-U peers are learned via signaling, not configured)"; }
    revision 2026-05-29 { description "Make gNBCUUPId config true so it can be set via NETCONF <edit-config>"; }
    revision 2026-05-28 { description "Add remote-control-extensions subtree"; }
    revision 2026-04-30 { description "Initial version"; }

    grouping gnbcuupfunction_extensions_subtree {

        container ocudu_gnbcuupfunction_extensions {
            description "OCUDU extension of GNBCUUPFunction";

            uses ocudu-log:log_extensions_subtree;
            uses ocudu-metrics:metrics_extensions_cuup_subtree;
            uses ocudu-pcap:pcap_extensions_subtree;
            uses ocudu-remote-control:remote_control_extensions_subtree;
            uses ocudu-trace:trace_extensions_cuup_subtree;
            uses ocudu-qos:qos_extensions_cuup_subtree;

            container ocudu_gnbcuupfunction_testmode_extensions {
                description "OCUDU CU-UP test mode: generates synthetic DL/UL user-plane
                             traffic without a real gNB-DU/core. Maps to the gNB-CU-UP
                             'cu_up.test_mode' config.";

                leaf enable {
                    description "Enable or disable CU-UP test mode.";
                    type boolean;
                    default false;
                }
                leaf integrity_enable {
                    description "Enable or disable PDCP integrity testing.";
                    type boolean;
                    default true;
                }
                leaf ciphering_enable {
                    description "Enable or disable PDCP ciphering testing.";
                    type boolean;
                    default true;
                }
                leaf nea_algo {
                    description "NEA (ciphering) algorithm to use for testing.";
                    type uint16 { range 0..3; }
                    default 2;
                }
                leaf nia_algo {
                    description "NIA (integrity) algorithm to use for testing.";
                    type uint16 { range 1..3; }
                    default 2;
                }
                leaf ue_ambr {
                    description "DL UE-AMBR used for testing, in bps.";
                    type uint64;
                    default 40000000000;
                }
                leaf attach_detach_period {
                    description "Attach/detach period for test mode, in milliseconds.
                                 0 means always attached.";
                    type uint32;
                    default 0;
                }
                leaf reestablish_period {
                    description "Reestablishment period for test mode, in milliseconds.
                                 0 means no re-establishments.";
                    type uint32;
                    default 0;
                }
                leaf f1u_peer_address {
                    description "Destination address for DL F1-U packets in test mode.";
                    type inet:ip-address;
                    default "127.0.10.2";
                }
                leaf nof_ues {
                    description "Number of UEs used for test mode.";
                    type uint32;
                    default 1;
                }
            }
        }
    }

    augment /me3gpp:ManagedElement/gnbcuup3gpp:GNBCUUPFunction {
        uses gnbcuupfunction_extensions_subtree;
    }

    deviation /me3gpp:ManagedElement/gnbcuup3gpp:GNBCUUPFunction/gnbcuup3gpp:attributes/gnbcuup3gpp:gNBCUUPId {
        deviate replace { config true; }
        description "3GPP marks gNBCUUPId as 'config false' (operational state), but OCUDU
                     provisions the CU-UP ID via NETCONF <edit-config> so it must be writable
                     in the running datastore.";
    }

    deviation /me3gpp:ManagedElement/gnbcuup3gpp:GNBCUUPFunction/ep3gpp:EP_E1/ep3gpp:attributes/ep3gpp:remoteAddress {
        deviate replace { type inet:host; }
        description "3GPP types EP_E1 remoteAddress as an IP address, but in Kubernetes
                     deployments the CU-CP E1 peer is reached via a DNS service name. Widen
                     to inet:host so an FQDN validates in the datastore; the O1 adapter
                     resolves it to an IP before writing the gNB config.";
    }

    deviation /me3gpp:ManagedElement/gnbcuup3gpp:GNBCUUPFunction/ep3gpp:EP_F1U/ep3gpp:attributes/ep3gpp:remoteAddress {
        deviate not-supported;
        description "F1-U is GTP-U: the peer (gNB-DU) transport address is learned via F1AP
                     bearer-context signaling, not statically configured. 3GPP marks
                     remoteAddress mandatory, so remove it to forbid it being set.";
    }

    deviation /me3gpp:ManagedElement/gnbcuup3gpp:GNBCUUPFunction/ep3gpp:EP_NgU/ep3gpp:attributes/ep3gpp:remoteAddress {
        deviate not-supported;
        description "NG-U (N3) is GTP-U: the UPF transport address is provided by the core via
                     NGAP/SMF, not statically configured. 3GPP marks remoteAddress mandatory,
                     so remove it to forbid it being set.";
    }

    augment /me3gpp:ManagedElement/gnbcuup3gpp:GNBCUUPFunction/ep3gpp:EP_F1U/ep3gpp:attributes {
        container ocudu_ep_f1u_extensions {
            description "OCUDU F1-U transport extensions. 3GPP EP_F1U models only the local
                         address (localAddress); these leaves add the GTP-U UDP ports.";

            leaf bind_port {
                type inet:port-number;
                default 2152;
                description "Local UDP port the F1-U (GTP-U) socket binds to.
                             Defaults to 2152 per 3GPP TS 29.281 Sec. 4.4.2.3.";
            }
            leaf peer_port {
                type inet:port-number;
                default 2152;
                description "Remote UDP port the F1-U (GTP-U) socket sends to.
                             Defaults to 2152 per 3GPP TS 29.281 Sec. 4.4.2.3.";
            }
        }
    }
}
