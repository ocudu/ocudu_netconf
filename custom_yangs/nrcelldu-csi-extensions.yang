// SPDX-FileCopyrightText: Copyright (C) 2021-2026 Software Radio Systems Limited
// SPDX-License-Identifier: BSD-3-Clause-Open-MPI

module nrcelldu-csi-extensions {
    yang-version 1.1;
    namespace "urn:ocudu-nrcelldu-csi-extension:1.0";
    prefix "ocudu-nrcelldu-csi";

    organization "Software Radio Systems Ltd";
    description "The module defines YANG extensions needed for OCUDU
                 Copyright (c) 2024-2026 Software Radio Systems. All rights reserved.";
    revision 2026-06-03 { description "Added csi_rs_enabled, meas/tracking/zp CSI-RS slot offsets,
                                       pwr_ctrl_offset and report_type."; }
    revision 2026-05-13 { description "Initial version"; }

    grouping csi_extensions_subtree {
        description "OCUDU Extension of 3gpp CSI config";

        container ocudu_nrcelldu_csi_extensions {
            leaf csi_rs_period {
                description "CSI-RS scheduling period in milliseconds";
                type uint16 { range "10 | 20 | 40 | 80"; }
                default "40";
            }
            leaf csi_rs_enabled {
                description "Enable CSI-RS resources and CSI reporting in the cell.";
                type boolean;
                default true;
            }
            leaf meas_csi_rs_slot_offset {
                description "Slot offset of the first CSI-RS resource used for measurement. If unset, OCUDU derives
                             it to avoid SSB/SIB1 collisions.";
                type uint16;
            }
            leaf tracking_csi_rs_slot_offset {
                description "Slot offset of the first CSI-RS resource used for tracking. If unset, OCUDU derives it
                             to avoid SSB/SIB1 collisions.";
                type uint16;
            }
            leaf zp_csi_rs_slot_offset {
                description "Slot offset for the ZP CSI-RS resources. If unset, OCUDU derives it to avoid SSB/SIB1
                             collisions.";
                type uint16;
            }
            leaf pwr_ctrl_offset {
                description "powerControlOffset: power offset of PDSCH RE to NZP CSI-RS RE, in dB.";
                type int8 { range "-8..15"; }
                default 0;
            }
            leaf report_type {
                description "Type of CSI reporting configuration to use.";
                type enumeration {
                    enum periodic;
                    enum aperiodic;
                }
                default periodic;
            }
        }
    }
}
