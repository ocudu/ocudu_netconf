// SPDX-FileCopyrightText: Copyright (C) 2021-2026 Software Radio Systems Limited
// SPDX-License-Identifier: BSD-3-Clause-Open-MPI

module nrcelldu-tdd-extensions {
    yang-version 1.1;
    namespace "urn:ocudu-nrcelldu-tdd-extension:1.0";
    prefix "ocudu-nrcelldu-tdd";
   
    organization "Software Radio Systems Ltd";
    description "The module defines YANG extensions needed for OCUDU
                 Copyright (c) 2024-2026 Software Radio Systems. All rights reserved.";
    revision 2026-06-03 { description "Added optional TDD pattern2 and aligned pattern1 ranges and defaults with the source."; }
    revision 2026-04-02 { description "Renamed srs instances to ocudu";}
    revision 2025-01-08 { description "Initial version"; }

    grouping tdd_extensions_subtree {
        description "OCUDU Extension of 3gpp TDD config";

        container ocudu_nrcelldu_tdd_extensions {
            leaf dl_ul_tx_period {
                description "TDD pattern periodicity in slots. The combination of this value and the chosen numerology must lead to a TDD periodicity of 0.5, 0.625, 1, 1.25, 2, 2.5, 3, 4, 5 or 10 milliseconds.";
                type int32 { range "2..80"; }
                default "10";
            }

            leaf nof_dl_slots {
                description "TDD pattern nof. consecutive full DL slots";
                type int32 { range "0..80"; }
                default "6";
            }

            leaf nof_dl_symbols {
                description "TDD pattern nof. DL symbols at the beginning of the slot following full DL slots";
                type int32 { range "0..13"; }
                default "8";
            }

            leaf nof_ul_slots {
                description "TDD pattern nof. consecutive full UL slots";
                type int32 { range "0..80"; }
                default "3";
            }            
            
            leaf nof_ul_symbols {
                description "TDD pattern nof. UL symbols at the end of the slot preceding the first full UL slot";
                type int32 { range "0..13"; }
                default "0";
            }

            container pattern2 {
                presence "Configure a second TDD UL/DL pattern. If absent, only pattern1 applies.";
                description "Optional second TDD UL/DL pattern.";

                leaf dl_ul_tx_period {
                    description "TDD pattern2 periodicity in slots. The combination of this value and the chosen
                                 numerology must lead to a TDD periodicity of 0.5, 0.625, 1, 1.25, 2, 2.5, 3, 4, 5
                                 or 10 milliseconds.";
                    type int32 { range "2..80"; }
                    default 10;
                }
                leaf nof_dl_slots {
                    description "TDD pattern2 nof. consecutive full DL slots.";
                    type int32 { range "0..80"; }
                    default 6;
                }
                leaf nof_dl_symbols {
                    description "TDD pattern2 nof. DL symbols at the beginning of the slot following full DL slots.";
                    type int32 { range "0..13"; }
                    default 8;
                }
                leaf nof_ul_slots {
                    description "TDD pattern2 nof. consecutive full UL slots.";
                    type int32 { range "0..80"; }
                    default 3;
                }
                leaf nof_ul_symbols {
                    description "TDD pattern2 nof. UL symbols at the end of the slot preceding the first full UL slot.";
                    type int32 { range "0..13"; }
                    default 0;
                }
            }
        }
    }
}
