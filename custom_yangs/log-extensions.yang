// SPDX-FileCopyrightText: Copyright (C) 2021-2026 Software Radio Systems Limited
// SPDX-License-Identifier: BSD-3-Clause-Open-MPI

module log-extensions {
    yang-version 1.1;
    namespace "urn:ocudu-log-extension:1.0";
    prefix "ocudu-log";

    organization "Software Radio Systems Ltd";
    description "The module defines YANG extensions needed for OCUDU
                 Copyright (c) 2024-2026 Software Radio Systems. All rights reserved.";
    revision 2026-11-06 { description "Added the remaining gNB log channel levels"; }
    revision 2026-05-05 { description "Renamed module to log-extensions; namespace, prefix, and container updated to drop function- prefix"; }
    revision 2026-04-30 { description "Renamed module to function-log-extensions for reuse across DU/CU/CUCP/CUUP"; }
    revision 2026-04-02 { description "Renamed srs instances to ocudu";}
    revision 2025-01-08 { description "Initial version"; }


    typedef log_level {
        type enumeration {
            enum debug {
                value 0;
                description "Debug level";
            }
            enum info {
                value 1;
                description "Info level";
            }
            enum warning {
                value 2;
                description "Warning level";
            }
            enum error {
                value 3;
                description "Error level";
            }
        }
        description "OCUDU log level enumeration";
    }

    grouping log_extensions_subtree {
        description "OCUDU log extensions reusable across DU/CU/CUCP/CUUP functions";

        container ocudu_log_extensions {

            leaf filename {
                description "Path of the log file";
                type string;
                default "/tmp/gnb.log";
            }

            leaf all_level {
                description "Log level for all log channels";
                type log_level;
                default warning;
            }

            leaf config_level {
                description "Log level for config handling (set to debug to print full config)";
                type log_level;
            }

            leaf phy_level {
                description "Log level for PHY";
                type log_level;
            }

            leaf mac_level {
                description "Log level for MAC";
                type log_level;
            }

            leaf rlc_level {
                description "Log level for RLC";
                type log_level;
            }

            leaf pdcp_level {
                description "Log level for PDCP";
                type log_level;
            }

            leaf rrc_level {
                description "Log level for RRC";
                type log_level;
            }   

            leaf sdap_level {
                description "Log level for SDAP";
                type log_level;
            }

            leaf ngap_level {
                description "Log level for NGAP";
                type log_level;
            }

            leaf gtpu_level {
                description "Log level for GTPU";
                type log_level;
            }

            leaf lib_level {
                description "Generic log level";
                type log_level;
            }

            leaf e2ap_level {
                description "Log level for E2AP";
                type log_level;
            }

            leaf fapi_level {
                description "Log level for FAPI";
                type log_level;
            }

            leaf ofh_level {
                description "Log level for Open Fronthaul";
                type log_level;
            }

            leaf radio_level {
                description "Log level for the SDR radio";
                type log_level;
            }

            leaf hal_level {
                description "Log level for HAL";
                type log_level;
            }

            leaf du_level {
                description "Log level for the DU";
                type log_level;
            }

            leaf f1ap_level {
                description "Log level for F1AP";
                type log_level;
            }

            leaf f1u_level {
                description "Log level for F1-U";
                type log_level;
            }

            leaf ntn_level {
                description "Log level for NTN";
                type log_level;
            }

            leaf cu_level {
                description "Log level for the CU";
                type log_level;
            }

            leaf xnap_level {
                description "Log level for XNAP";
                type log_level;
            }

            leaf nrppa_level {
                description "Log level for NRPPA";
                type log_level;
            }

            leaf e1ap_level {
                description "Log level for E1AP";
                type log_level;
            }

            leaf sec_level {
                description "Log level for security functions";
                type log_level;
            }
        }        
    }
}
