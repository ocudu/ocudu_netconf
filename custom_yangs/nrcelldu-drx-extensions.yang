// SPDX-FileCopyrightText: Copyright (C) 2021-2026 Software Radio Systems Limited
// SPDX-License-Identifier: BSD-3-Clause-Open-MPI

module nrcelldu-drx-extensions {
    yang-version 1.1;
    namespace "urn:ocudu-nrcelldu-drx-extension:1.0";
    prefix "ocudu-nrcelldu-drx";

    organization "Software Radio Systems Ltd";
    description "The module defines YANG extensions needed for OCUDU
                 Copyright (c) 2024-2026 Software Radio Systems. All rights reserved.";
    revision 2026-06-03 { description "Initial version: DRX configuration (DRX-Config, TS 38.331)."; }

    grouping drx_extensions_subtree {
        description "OCUDU extension of 3gpp DRX (DRX-Config) config";

        container ocudu_nrcelldu_drx_extensions {
            leaf on_duration_timer {
                description "drx-onDurationTimer in milliseconds: minimum time the UE stays active when DRX is configured.";
                type uint16 {
                    range "1 | 2 | 3 | 4 | 5 | 6 | 8 | 10 | 20 | 30 | 40 | 50 | 60 | 80 | 100 | 200 | 300 | 400 | 500 | 600 | 800 | 1000 | 1200 | 1600";
                }
                default 10;
            }
            leaf inactivity_timer {
                description "drx-InactivityTimer in milliseconds: time the UE stays active after PDCCH reception.";
                type uint16 {
                    range "0 | 1 | 2 | 3 | 4 | 5 | 6 | 8 | 10 | 20 | 30 | 40 | 50 | 60 | 80 | 100 | 200 | 300 | 500 | 750 | 1280 | 1920 | 2560";
                }
                default 0;
            }
            leaf retx_timer_dl {
                description "drx-RetransmissionTimerDL in slots: maximum time until a DL retransmission is received by the UE.";
                type uint16 { range "0 | 1 | 2 | 4 | 6 | 8 | 16 | 24 | 33 | 40 | 64 | 80 | 96 | 112 | 128 | 160 | 320"; }
                default 0;
            }
            leaf retx_timer_ul {
                description "drx-RetransmissionTimerUL in slots: maximum time until a grant for a UL retransmission is received by the UE.";
                type uint16 { range "0 | 1 | 2 | 4 | 6 | 8 | 16 | 24 | 33 | 40 | 64 | 80 | 96 | 112 | 128 | 160 | 320"; }
                default 0;
            }
            leaf long_cycle {
                description "drx-LongCycle in milliseconds between UE DRX long cycles. The value 0 disables DRX.";
                type uint16 {
                    range "0 | 10 | 20 | 32 | 40 | 60 | 64 | 70 | 80 | 128 | 160 | 256 | 320 | 512 | 640 | 1024 | 1280 | 2048 | 2560 | 5120 | 10240";
                }
                default 0;
            }
        }
    }
}
