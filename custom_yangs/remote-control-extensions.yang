// SPDX-FileCopyrightText: Copyright (C) 2021-2026 Software Radio Systems Limited
// SPDX-License-Identifier: BSD-3-Clause-Open-MPI

module remote-control-extensions {
    yang-version 1.1;
    namespace "urn:ocudu-remote-control-extensions:1.0";
    prefix "ocudu-remote-control";

    import ietf-inet-types { prefix inet; }

    organization "Software Radio Systems Ltd";
    description "The module defines YANG extensions needed for OCUDU
                 Copyright (c) 2024-2026 Software Radio Systems. All rights reserved.";
    revision 2026-06-23 { description "Add configurable remote control server listen port"; }
    revision 2026-04-02 { description "Renamed srs instances to ocudu";}
    revision 2025-01-08 { description "Initial version"; }

    grouping remote_control_extensions_subtree {
        description "OCUDU extensions for remote control configuration.";

        container ocudu_remote_control_extensions {
            description "Remote control specific configuration options.";

            leaf enabled {
                description "Enable or disable the remote control service.";
                type boolean;
                default "true";
            }

            leaf bind_addr {
                description "IP address that the remote control service binds to.";
                type inet:ip-address;
                default "0.0.0.0";
            }

            leaf port {
                description "TCP port that the remote control service listens on for incoming connections.";
                type inet:port-number;
                default 8001;
            }
        }
    }
}
