// SPDX-FileCopyrightText: Copyright (C) 2021-2026 Software Radio Systems Limited
// SPDX-License-Identifier: BSD-3-Clause-Open-MPI

module gnbdufunction-testmode-extensions {
    yang-version 1.1;
    namespace "urn:ocudu-gnbdufunction-testmode-extension:1.0";
    prefix "ocudu-gnbdufunction-testmode";


    organization "Software Radio Systems Ltd";
    description "The module defines YANG extensions needed for OCUDU
                 Copyright (c) 2024-2026 Software Radio Systems. All rights reserved.";
    revision 2026-04-02 { description "Renamed srs instances to ocudu";}
    revision 2025-01-08 { description "Initial version"; }


    grouping testmode_extensions_subtree {
        description "OCUDU Extension of GNBDUFunction";

        container ocudu_gnbdufunction_testmode_extensions {

            leaf enabled {
                description "Set to enable to attach test UEs";
                type boolean;
                default false;
            }

            leaf rnti {
                description "RNTI of test UE";
                type int32 { range 1..65519; }
                default "44";
            }

            leaf ri {
                description "Rank indicator reported by UE";
                type int32 { range 1..4; }
                default "1";
            }

            leaf cqi {
                description "CQI reported by UE";
                type int32 { range 1..15; }
                default "15";
            }

            leaf nof_ues {
                description "Number of UEs to attach";
                type int32 { range 1..128; }
                default "1";
            }

            leaf pdsch_active {
                description "Whether to enable DL transmissions for active UEs";
                type boolean;
                default true;
            }

            leaf pusch_active {
                description "Whether to enable UL transmissions for active UEs";
                type boolean;
                default true;
            }
        }        
    }
}
